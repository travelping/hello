module handler2 {
    namespace "hello_test";
    prefix "handler2";

    rpc fun1 {
        input {
        	leaf arg1 {
        		type string;
        	}
        }
    }

    rpc fun2 {
        input {
        	leaf arg1 {
        		type string;
        	}
        }
    }

    rpc fun3 {
        input {
        	leaf arg1 {
        		type string;
        	}
        }
    }

    rpc fun4 {
        input {
        	leaf arg1 {
        		type string;
        	}
        }
    }
    
    rpc fun5 {
        input {
            leaf arg1 {
                type string;
            }
        }
    }

}
