module hello_example {
    namespace "http://travelping.com/ns/hello/example";
    prefix "";

    typedef Status {
         type enumeration {
            enum ok;
            enum error;
        }
    }

    grouping rpc_error {
        leaf code {
            type int16;
        }
        leaf message {
            type string;
        }
    }

    grouping result {
        leaf Status {
            description "Result of this operation";
            type Status;
        }
        choice result {
            case error {
                when "Status = 'error'";
                uses rpc_error;
            }
            case ok {
                when "Status = 'ok'";
                choice Data {
                    case Boolean {
                        leaf Ok {
                            type boolean;
                        }
                    }
                    case Items {
                        container Result;
                    }
                }
            }
        }
    }

    rpc echo {
        input {
            leaf text {
                type string;
                default "";
            }
        }
        output {
            uses result;
        }
    }
    rpc delay {
        input {
            leaf delay {
                type int64;
                default 1000;
            }
        }
        output {
            uses result;
        }
    }
    rpc append {
        input {
            leaf str1 {
                type string;
                default "";
            }
            leaf str2 {
                type string;
                default "";
            }
        }
        output {
            uses result;
        }
    }
    rpc enum_test {
        input {
            leaf atom {
                type enumeration {
                    enum a;
                    enum b;
                    enum c;
                }
            }
        }
        output {
            uses result;
        }
    }
    rpc return_error {
        input {
            uses rpc_error;
        }
        output {
            uses result;
        }
    }
}
